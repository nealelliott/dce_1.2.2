-- 
-- @OSF_COPYRIGHT@
-- COPYRIGHT NOTICE
-- Copyright (c) 1990, 1991, 1992, 1993, 1994, 1996 Open Software Foundation, Inc.
-- ALL RIGHTS RESERVED (DCE).  See the file named COPYRIGHT.DCE for
-- the full copyright text.
-- 
-- HISTORY
-- $Log: gdsauth.asn1,v $
-- Revision 1.1.4.2  1996/03/09  23:12:49  marty
-- 	Update OSF copyright year
-- 	[1996/03/09  22:29:58  marty]
--
-- Revision 1.1.4.1  1995/12/08  15:22:38  root
-- 	Submit OSF/DCE 1.2.1
-- 	[1995/12/08  14:53:14  root]
-- 
-- Revision 1.1.2.3  1994/08/10  08:25:24  marrek
-- 	Fix for SAP errors, OT11467.
-- 	[1994/08/08  14:13:28  marrek]
-- 
-- Revision 1.1.2.2  1994/06/09  18:44:37  devsrc
-- 	cr10871 - expand copyright
-- 	[1994/06/09  18:17:20  devsrc]
-- 
-- Revision 1.1.2.1  1994/02/22  19:20:50  marrek
-- 	Change rcsid string format.
-- 	[1994/02/09  08:10:23  marrek]
-- 
-- 	Creation for dce1.1.
-- 	[1994/02/02  10:51:37  marrek]
-- 
-- $EndLog$

-- $RCSfile: gdsauth.asn1,v $ $Revision: 1.1.4.2 $ $Date: 1996/03/09 23:12:49 $

gdsauth
DEFINITIONS ::=
BEGIN

duaCertUnsigned	::= SEQUENCE{
			version	[0] 	INTEGER,
			serialNumber	INTEGER,
			signature	duaAlgId,
			issuer		ANY,
			validity	duaValidity,
			subject		ANY,
			subjectPublicKeyInfo duaSubjectPublicKeyInfo}

duaCertificate ::= SEQUENCE {
			unsCert duaCertUnsigned,
			signature duaAlgId,
			encrOctString BIT STRING}

duaValidity	::= SEQUENCE{
			notBefore	UTCTime,
			notAfter	UTCTime}

duaSubjectPublicKeyInfo ::= SEQUENCE{
				algorithm	 duaAlgId,
				subjectPublicKey BIT STRING}

duaAlgId  ::= SEQUENCE{
			   algorithm	OBJECT ID,
			   parameters   INTEGER OPTIONAL }

-- duaCertificates	::= SEQUENCE{
			-- certificate	  duaCertificate,
			-- certificationPath duaForwardCertificationPath OPTIONAL}

-- duaForwardCertificationPath ::= SEQUENCE OF duaCrossCertificates

-- duaCertificationPath	::= SEQUENCE{
				-- userCertificate		duaCertificate,
				-- theCACertificates SEQUENCE OF duaCertificatePair
								-- OPTIONAL}

-- duaCrossCertificates ::= SET OF duaCertificate

duaRCUns ::= SEQUENCE OF SEQUENCE{
		signature	duaAlgId,
		issuer		ANY,
		userCertificate	INTEGER,
		revocationDate	UTCTime}

duaRevokedCertificates ::= SEQUENCE {
			unsRev duaRCUns,
			signature duaAlgId,
			encrOctString BIT STRING}

duaCertListUnsigned ::= SEQUENCE{
			signature		duaAlgId,
			issuer			ANY,
			lastUpdate		UTCTime,
			revokedCertificates duaRevokedCertificates OPTIONAL}

duaCertList ::= SEQUENCE {
		unsCertList duaCertListUnsigned,
		signature duaAlgId,
		encrOctString BIT STRING}

duaCertPair ::= SEQUENCE{
			forward [0]	duaCertificate OPTIONAL,
			reverse [1]	duaCertificate OPTIONAL}

END -- of auth
