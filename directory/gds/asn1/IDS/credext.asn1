-- @OSF_COPYRIGHT@
-- COPYRIGHT NOTICE
-- Copyright (c) 1990, 1991, 1992, 1993, 1994, 1996 Open Software Foundation, Inc.
-- ALL RIGHTS RESERVED (DCE).  See the file named COPYRIGHT.DCE for
-- the full copyright text.
-- 
-- HISTORY
-- $Log: credext.asn1,v $
-- Revision 1.1.4.2  1996/03/09  23:12:52  marty
-- 	Update OSF copyright year
-- 	[1996/03/09  22:30:00  marty]
--
-- Revision 1.1.4.1  1995/12/08  15:22:55  root
-- 	Submit OSF/DCE 1.2.1
-- 	[1995/12/08  14:53:18  root]
-- 
-- Revision 1.1.2.3  1994/07/06  15:06:35  marrek
-- 	July 1994 code drop.
-- 	[1994/07/06  10:00:40  marrek]
-- 
-- Revision 1.1.2.2  1994/06/09  18:44:38  devsrc
-- 	cr10871 - expand copyright
-- 	[1994/06/09  18:17:21  devsrc]
-- 
-- Revision 1.1.2.1  1994/05/10  16:14:22  marrek
-- 	comment leader was wrong
-- 	[1994/04/28  08:50:03  marrek]
-- 
-- 	Created for April Submission.
-- 	[1994/04/26  12:49:23  marrek]
-- 
-- $EndLog$
-- 
-- $RCSfile: credext.asn1,v $ $Revision: 1.1.4.2 $ $Date: 1996/03/09 23:12:52 $

credext
DEFINITIONS ::=
BEGIN

GdsExternal ::= [UNIVERSAL 8] IMPLICIT SEQUENCE {
			directReference OBJECT ID OPTIONAL,
			indirectReference INTEGER OPTIONAL,
			dataValueDescriptor ObjectDescriptor OPTIONAL,
			encoding CHOICE {
				singleASN1Type [0] ANY,
				octetAligned   [1] IMPLICIT OCTET STRING,
				arbitrary      [2] IMPLICIT BIT STRING }}

END
